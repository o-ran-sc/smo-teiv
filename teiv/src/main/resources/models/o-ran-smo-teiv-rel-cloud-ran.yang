module o-ran-smo-teiv-rel-cloud-ran {
    yang-version 1.1;
    namespace "urn:o-ran:smo-teiv-rel-cloud-ran";
    prefix or-teiv-cloudtoran;

    import o-ran-smo-teiv-common-yang-types {prefix or-teiv-types; }

    import o-ran-smo-teiv-common-yang-extensions {prefix or-teiv-yext; }

    import o-ran-smo-teiv-cloud {prefix or-teiv-cloud; }

    import o-ran-smo-teiv-ran {prefix or-teiv-ran; }

    organization "ORAN";
    contact "The Authors";
    description
        "RAN Cloud to RAN Logical topology model.

        This model contains the RAN Cloud to RAN Logical topology relations.

        Copyright (C) 2024 Ericsson
        Modifications Copyright (C) 2024 OpenInfra Foundation Europe

        Licensed under the Apache License, Version 2.0 (the \"License\");
        you may not use this file except in compliance with the License.
        You may obtain a copy of the License at

        http://www.apache.org/licenses/LICENSE-2.0

        Unless required by applicable law or agreed to in writing, software
        distributed under the License is distributed on an \"AS IS\" BASIS,
        WITHOUT WARRANTIES OR CONDITIONS OF ANY KIND, either express or implied.
        See the License for the specific language governing permissions and
        limitations under the License.

        SPDX-License-Identifier: Apache-2.0";

    revision "2024-10-04" {
        description "Added grouping, Origin_Relationship_Mapping_Grp to the topology object.";
        or-teiv-yext:label 0.4.0;
    }

    revision "2024-05-02" {
        description "Initial revision.";
        or-teiv-yext:label 0.3.0;
    }

    revision "2024-07-15" {
        description "This revision aligns O-RAN Work Group 10 Stage 2 Specification (O-RAN.WG10.TE&IV-CIMI.0-R004.v02.00)";
        or-teiv-yext:label 0.4.0;
    }

    or-teiv-yext:domain REL_CLOUD_RAN;

    or-teiv-yext:biDirectionalTopologyRelationship NFDEPLOYMENT_SERVES_ODUFUNCTION { // 0..n to 0..m

        uses or-teiv-types:Top_Grp_Type;
        uses or-teiv-types:Origin_Relationship_Mapping_Grp;
        key id;

        leaf-list serviced-oduFunction {
            description "O-DU Function serviced by this NF Deployment.";
            or-teiv-yext:aSide or-teiv-cloud:NFDeployment;
            type instance-identifier;
        }

        leaf-list serving-nFDeployment {
            description "NF Deployment that serves this O-DU Function.";
            or-teiv-yext:bSide or-teiv-ran:ODUFunction;
            type instance-identifier;
        }
    }

    or-teiv-yext:biDirectionalTopologyRelationship NFDEPLOYMENT_SERVES_OCUCPFUNCTION { // 0..n to 0..m

        uses or-teiv-types:Top_Grp_Type;
        uses or-teiv-types:Origin_Relationship_Mapping_Grp;
        key id;

        leaf-list serviced-ocucpFunction {
            description "O-CU-CP Function serviced by this NF Deployment.";
            or-teiv-yext:aSide or-teiv-cloud:NFDeployment;
            type instance-identifier;
        }

        leaf-list serving-nFDeployment {
            description "NF Deployment that serves this O-CU-CP Function.";
            or-teiv-yext:bSide or-teiv-ran:OCUCPFunction;
            type instance-identifier;
        }
    }

    or-teiv-yext:biDirectionalTopologyRelationship NFDEPLOYMENT_SERVES_OCUUPFUNCTION { // 0..n to 0..m

        uses or-teiv-types:Top_Grp_Type;
        uses or-teiv-types:Origin_Relationship_Mapping_Grp;
        key id;

        leaf-list serviced-ocuupFunction {
            description "O-CU-UP Function serviced by this NF Deployment.";
            or-teiv-yext:aSide or-teiv-cloud:NFDeployment;
            type instance-identifier;
        }

        leaf-list serving-nFDeployment {
            description "NF Deployment that serves this O-CU-UP Function.";
            or-teiv-yext:bSide or-teiv-ran:OCUUPFunction;
            type instance-identifier;
        }
    }

    or-teiv-yext:biDirectionalTopologyRelationship NFDEPLOYMENT_SERVES_NEARRTRICFUNCTION { // 0..n to 0..m

        uses or-teiv-types:Top_Grp_Type;
        uses or-teiv-types:Origin_Relationship_Mapping_Grp;
        key id;

        leaf-list serviced-nearRTRICFunction {
            description "NearRTRICFunction serviced by this NF Deployment.";
            or-teiv-yext:aSide or-teiv-cloud:NFDeployment;
            type instance-identifier;
        }

        leaf-list serving-nFDeployment {
            description "NF Deployment that serves this NearRTRICFunction.";
            or-teiv-yext:bSide or-teiv-ran:NearRTRICFunction;
            type instance-identifier;
        }
    }
}
