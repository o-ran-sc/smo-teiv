module o-ran-smo-teiv-rel-oam-ran {
    yang-version 1.1;
    namespace "urn:o-ran:smo-teiv-rel-oam-ran";
    prefix or-teiv-rel-oamran;

    import o-ran-smo-teiv-common-yang-types { prefix or-teiv-types; }

    import o-ran-smo-teiv-common-yang-extensions { prefix or-teiv-yext; }

    import o-ran-smo-teiv-oam { prefix or-teiv-oam; }

    import o-ran-smo-teiv-ran { prefix or-teiv-ran; }

    organization "ORAN";
    contact "The Authors";
    description
        "RAN O&M to Logical topology model.

        This model contains the RAN O&M to Logical topology relations

        Copyright (C) 2024 Ericsson
        Modifications Copyright (C) 2024 OpenInfra Foundation Europe

        Licensed under the Apache License, Version 2.0 (the \"License\");
        you may not use this file except in compliance with the License.
        You may obtain a copy of the License at

        http://www.apache.org/licenses/LICENSE-2.0

        Unless required by applicable law or agreed to in writing, software
        distributed under the License is distributed on an \"AS IS\" BASIS,
        WITHOUT WARRANTIES OR CONDITIONS OF ANY KIND, either express or implied.
        See the License for the specific language governing permissions and
        limitations under the License.

        SPDX-License-Identifier: Apache-2.0";

    revision "2024-10-04" {
        description "Added grouping, Origin_Relationship_Mapping_Grp to the topology object.";
        or-teiv-yext:label 0.5.0;
    }

    revision "2024-07-15" {
        description "This revision aligns O-RAN Work Group 10 Stage 2 Specification (O-RAN.WG10.TE&IV-CIMI.0-R004.v02.00)";
        or-teiv-yext:label 0.4.0;
    }

    revision "2024-05-24" {
        description "Initial revision.";
        or-teiv-yext:label 0.3.0;
    }

    or-teiv-yext:domain REL_OAM_RAN;

    or-teiv-yext:biDirectionalTopologyRelationship MANAGEDELEMENT_MANAGES_ODUFUNCTION {    // 1 to 0..n

        description
            "The aSide of this relationship is an instance of the ManagedElement type.
            The bSide of this relationship is an instance of the ODUFunction type.
            The ManagedElement represents the node that manages the ODUFunction.
            A ManagedElement instance can manage many ODUFunctions.
            An ODUFunction instance must be managed by one ManagedElement.
            ";

        uses or-teiv-types:Top_Grp_Type;
        uses or-teiv-types:Origin_Relationship_Mapping_Grp;
        key id;

        leaf-list managed-oduFunction {
            description "Managed Element manages O-DU Function.";
            or-teiv-yext:aSide or-teiv-oam:ManagedElement;
            type instance-identifier;
        }

        leaf managed-by-managedElement {
            description "O-DU Function managed by Managed Element.";
            or-teiv-yext:bSide or-teiv-ran:ODUFunction;
            type instance-identifier;
            mandatory true;
        }
    }

    or-teiv-yext:biDirectionalTopologyRelationship MANAGEDELEMENT_MANAGES_OCUCPFUNCTION {    // 1 to 0..n

        description
            "The aSide of this relationship is an instance of the ManagedElement type.
            The bSide of this relationship is an instance of the OCUCPFunction type.
            The ManagedElement represents the node that manages the OCUCPFunction.
            A ManagedElement instance can manage many OCUCPFunctions.
            An OCUCPFunction instance must be managed by one ManagedElement.
            ";

        uses or-teiv-types:Top_Grp_Type;
        uses or-teiv-types:Origin_Relationship_Mapping_Grp;
        key id;

        leaf-list managed-ocucpFunction {
            description "Managed Element manages O-CU-CP Function.";
            or-teiv-yext:aSide or-teiv-oam:ManagedElement;
            type instance-identifier;
        }

        leaf managed-by-managedElement {
            description "O-CU-CP Function managed by Managed Element.";
            or-teiv-yext:bSide or-teiv-ran:OCUCPFunction;
            type instance-identifier;
            mandatory true;
        }
    }

    or-teiv-yext:biDirectionalTopologyRelationship MANAGEDELEMENT_MANAGES_OCUUPFUNCTION {    // 1 to 0..n

        description
            "The aSide of this relationship is an instance of the ManagedElement type.
            The bSide of this relationship is an instance of the OCUUPFunction type.
            The ManagedElement represents the node that manages the OCUUPFunction.
            A ManagedElement instance can manage many OCUUPFunctions.
            An OCUUPFunction instance must be managed by one ManagedElement.
            ";

        uses or-teiv-types:Top_Grp_Type;
        uses or-teiv-types:Origin_Relationship_Mapping_Grp;
        key id;

        leaf-list managed-ocuupFunction {
            description "Managed Element manages O-CU-UP Function.";
            or-teiv-yext:aSide or-teiv-oam:ManagedElement;
            type instance-identifier;
        }

        leaf managed-by-managedElement {
            description "O-CU-UP Function managed by Managed Element.";
            or-teiv-yext:bSide or-teiv-ran:OCUUPFunction;
            type instance-identifier;
            mandatory true;
        }
    }

    or-teiv-yext:biDirectionalTopologyRelationship MANAGEDELEMENT_MANAGES_ORUFUNCTION {    // 1 to 0..n

        description
            "The aSide of this relationship is an instance of the ManagedElement type.
            The bSide of this relationship is an instance of the ORUFunction type.
            The ManagedElement represents the node that manages the ORUFunction.
            A ManagedElement instance can manage many ORUFunction.
            An ORUFunction instance must be managed by one ManagedElement.
            ";

        uses or-teiv-types:Top_Grp_Type;
        uses or-teiv-types:Origin_Relationship_Mapping_Grp;
        key id;

        leaf-list managed-oruFunction {
            description "Managed Element manages O-RU Function.";
            or-teiv-yext:aSide or-teiv-oam:ManagedElement;
            type instance-identifier;
        }

        leaf managed-by-managedElement {
            description "O-RU Function managed by Managed Element.";
            or-teiv-yext:bSide or-teiv-ran:ORUFunction;
            type instance-identifier;
            mandatory true;
        }
    }

    or-teiv-yext:biDirectionalTopologyRelationship MANAGEDELEMENT_MANAGES_NEARRTRICFUNCTION {    // 1 to 0..n

        description
            "The aSide of this relationship is an instance of the ManagedElement type.
            The bSide of this relationship is an instance of the NearRTRICFunction type.
            The ManagedElement represents the node that manages the NearRTRICFunction.
            A ManagedElement instance can manage many NearRTRICFunction.
            An NearRTRICFunction instance must be managed by one ManagedElement.
            ";

        uses or-teiv-types:Top_Grp_Type;
        uses or-teiv-types:Origin_Relationship_Mapping_Grp;
        key id;

        leaf-list managed-nearRTRICFunction {
            description "Managed Element manages Near RT RIC Function.";
            or-teiv-yext:aSide or-teiv-oam:ManagedElement;
            type instance-identifier;
        }

        leaf managed-by-managedElement {
            description "Near RT RIC Function managed by Managed Element.";
            or-teiv-yext:bSide or-teiv-ran:NearRTRICFunction;
            type instance-identifier;
            mandatory true;
        }
    }
}
