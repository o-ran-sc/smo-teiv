module o-ran-smo-teiv-oam-to-cloud {
    yang-version 1.1;
    namespace "urn:o-ran:smo-teiv-oam-to-cloud";
    prefix or-teiv-oamtocloud;

    import o-ran-smo-teiv-common-yang-types {prefix or-teiv-types; }

    import o-ran-smo-teiv-common-yang-extensions {prefix or-teiv-yext; }

    import o-ran-smo-teiv-oam {prefix or-teiv-oam; }

    import o-ran-smo-teiv-cloud {prefix or-teiv-cloud; }

    organization "ORAN";
    contact "The Authors";
    description 
    "RAN O&M to Cloud topology model.

    This model contains the RAN O&M to Cloud topology relations

    Copyright (C) 2024 Ericsson
    Modifications Copyright (C) 2024 OpenInfra Foundation Europe

    Licensed under the Apache License, Version 2.0 (the \"License\");
    you may not use this file except in compliance with the License.
    You may obtain a copy of the License at

    http://www.apache.org/licenses/LICENSE-2.0

    Unless required by applicable law or agreed to in writing, software
    distributed under the License is distributed on an \"AS IS\" BASIS,
    WITHOUT WARRANTIES OR CONDITIONS OF ANY KIND, either express or implied.
    See the License for the specific language governing permissions and
    limitations under the License.

    SPDX-License-Identifier: Apache-2.0";

    revision "2024-05-02" {
        description "Initial revision.";
        or-teiv-yext:label 0.3.0;
    }

    or-teiv-yext:domain OAM_TO_CLOUD;

    or-teiv-yext:biDirectionalTopologyRelationship MANAGEDELEMENT_DEPLOYED_AS_CLOUDIFIEDNF {  // 0..1 to 1

        uses or-teiv-types:Top_Grp_Type;
        key id;

        leaf deployed-as-cloudifiedNF {
            description "Managed Element deployed as Cloudified NF.";
            or-teiv-yext:aSide or-teiv-oam:ManagedElement;
            type instance-identifier;
        }

        leaf deployed-managedElement {
            description "Cloudified NF deploys Managed Element.";
            or-teiv-yext:bSide or-teiv-cloud:CloudifiedNF;
            type instance-identifier;
            mandatory true;
        }
    }

    or-teiv-yext:biDirectionalTopologyRelationship NFDEPLOYMENT_SERVES_MANAGEDELEMENT { // 1..n to 1

        uses or-teiv-types:Top_Grp_Type;
        key id;

        leaf serviced-managedElement {
            description "Managed Element serviced by this NF Deployment.";
            or-teiv-yext:aSide or-teiv-cloud:NFDeployment;
            type instance-identifier;
            mandatory true;
        }

        leaf-list serving-nFDeployment {
            description "NF Deployment that serves this Managed Element.";
            or-teiv-yext:bSide or-teiv-oam:ManagedElement;
            type instance-identifier;
            min-elements 1;
        }
    }
}
