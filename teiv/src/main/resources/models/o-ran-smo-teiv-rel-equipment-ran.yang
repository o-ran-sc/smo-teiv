module o-ran-smo-teiv-rel-equipment-ran {
    yang-version 1.1;
    namespace "urn:o-ran:smo-teiv-rel-equipment-ran";
    prefix or-teiv-rel-equipran;

    import o-ran-smo-teiv-common-yang-types { prefix or-teiv-types; }

    import o-ran-smo-teiv-common-yang-extensions { prefix or-teiv-yext; }

    import o-ran-smo-teiv-equipment { prefix or-teiv-equip; }

    import o-ran-smo-teiv-ran { prefix or-teiv-ran; }


    organization "ORAN";
    contact "The Authors";
    description 
    "RAN Equipment to Logical topology model.

    This model contains the RAN Equipment to Logical topology
    entities and relations.

    Copyright (C) 2024 Ericsson
    Modifications Copyright (C) 2024 OpenInfra Foundation Europe

    Licensed under the Apache License, Version 2.0 (the \"License\");
    you may not use this file except in compliance with the License.
    You may obtain a copy of the License at

    http://www.apache.org/licenses/LICENSE-2.0

    Unless required by applicable law or agreed to in writing, software
    distributed under the License is distributed on an \"AS IS\" BASIS,
    WITHOUT WARRANTIES OR CONDITIONS OF ANY KIND, either express or implied.
    See the License for the specific language governing permissions and
    limitations under the License.

    SPDX-License-Identifier: Apache-2.0";

    revision "2024-10-08" {
        description
            "Added new relationship ANTENNAMODULE_SERVES_NRCELLDU.";
        or-teiv-yext:label 0.5.0;
    }

    revision "2024-10-04" {
        description "Added grouping, Origin_Relationship_Mapping_Grp to the topology object.";
        or-teiv-yext:label 0.4.0;
    }

    revision "2024-05-24" {
        description "Initial revision.";
        or-teiv-yext:label 0.3.0;
    }

    or-teiv-yext:domain REL_EQUIPMENT_RAN;

    or-teiv-yext:biDirectionalTopologyRelationship ANTENNAMODULE_SERVES_ANTENNACAPABILITY { // 0..n to 0..m

        description
            "The aSide of this relationship is an instance of the AntennaModule type.
            The bSide of this relationship is an instance of the AntennaCapability type.
            The AntennaModule represents the physical antenna that serves the AntennaCapability.
            An AntennaModule instance can serve many AntennaCapabilities.
            An AntennaCapability instance can be served by many AntennaModules.
            ";

        uses or-teiv-types:Top_Grp_Type;
        uses or-teiv-types:Origin_Relationship_Mapping_Grp;
        key id;

        leaf-list serviced-antennaCapability {
            description "Antenna Capability serviced by this Antenna Module.";
            or-teiv-yext:aSide or-teiv-equip:AntennaModule;
            type instance-identifier;
        }

        leaf-list serving-antennaModule {
            description "Antenna Module serves this Antenna Capability.";
            or-teiv-yext:bSide or-teiv-ran:AntennaCapability;
            type instance-identifier;
        }
    }

    or-teiv-yext:biDirectionalTopologyRelationship ANTENNAMODULE_SERVES_NRCELLDU { // 1..n to 0..m

        description
            "The aSide of this relationship is an instance of the AntennaModule type.
            The bSide of this relationship is an instance of the NRCellDU type.
            The AntennaModule represents the physical antenna that serves the NRCellDU.
            An AntennaModule instance can serve many NRCellDUs.
            An NRCellDU instance can be served by many AntennaModules.
            ";

        uses or-teiv-types:Top_Grp_Type;
        uses or-teiv-types:Origin_Relationship_Mapping_Grp;
        key id;

        leaf-list serviced-nrCellDu {
            description "NR Cell-DU serviced by this Antenna Module.";
            or-teiv-yext:aSide or-teiv-equip:AntennaModule;
            type instance-identifier;
        }

        leaf-list serving-antennaModule {
            description "Antenna Module serves this NR Cell-DU.";
            or-teiv-yext:bSide or-teiv-ran:NRCellDU;
            type instance-identifier;
            min-elements 1;
        }
    }

    or-teiv-yext:biDirectionalTopologyRelationship SECTOR_GROUPS_ANTENNAMODULE { // 0..1 to 0..n

        description
            "The aSide of this relationship is an instance of the Sector type.
            The bSide of this relationship is an instance of the AntennaModule type.
            The Sector represents the geographical area that groups the AntennaModules.
            A Sector instance can group many AntennaModules.
            An AntennaModule instance can only be grouped by one Sector.
            ";

        uses or-teiv-types:Top_Grp_Type;
        uses or-teiv-types:Origin_Relationship_Mapping_Grp;
        key id;

        leaf-list grouped-antennaModule {
            description "Sector groups Antenna Module.";
            or-teiv-yext:aSide or-teiv-ran:Sector;
            type instance-identifier;
        }

        leaf grouped-by-sector {
            description "Antenna Module grouped by Sector.";
            or-teiv-yext:bSide or-teiv-equip:AntennaModule;
            type instance-identifier;
        }
    }
}
