module o-ran-smo-teiv-oam {
    yang-version 1.1;
    namespace "urn:o-ran:smo-teiv-oam";
    prefix or-teiv-oam;

    import o-ran-smo-teiv-common-yang-types { prefix or-teiv-types; }

    import o-ran-smo-teiv-common-yang-extensions { prefix or-teiv-yext; }

    organization "ORAN";
    contact "The Authors";
    description 
    "RAN O&M topology model.

    This model contains the topology entities and relations in the
    RAN O&M domain, which are intended to represent management systems
    and management interfaces.

    Copyright (C) 2024 Ericsson
    Modifications Copyright (C) 2024 OpenInfra Foundation Europe

    Licensed under the Apache License, Version 2.0 (the \"License\");
    you may not use this file except in compliance with the License.
    You may obtain a copy of the License at

    http://www.apache.org/licenses/LICENSE-2.0

    Unless required by applicable law or agreed to in writing, software
    distributed under the License is distributed on an \"AS IS\" BASIS,
    WITHOUT WARRANTIES OR CONDITIONS OF ANY KIND, either express or implied.
    See the License for the specific language governing permissions and
    limitations under the License.

    SPDX-License-Identifier: Apache-2.0";

    revision "2024-10-04" {
        description "Added grouping, Origin_Entity_Mapping_Grp to the topology object.";
        or-teiv-yext:label 0.4.0;
    }

    revision "2024-05-24" {
        description "Initial revision.";
        or-teiv-yext:label 0.3.0;
    }

    or-teiv-yext:domain OAM;

    list ManagedElement {
        description "A Managed Element (ME) is a node into a telecommunication
        network providing support and/or service to subscribers. An ME
        communicates with a manager application (directly or indirectly)
        over one or more interfaces for the purpose of being monitored
        and/or controlled.";

        uses or-teiv-types:Top_Grp_Type;
        uses or-teiv-types:Origin_Entity_Mapping_Grp;
        key id;
    }
}
